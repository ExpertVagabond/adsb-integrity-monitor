# ADS-B Integrity Monitor: System Requirements
Generated by `python -m aim reqif` from docs/02-Requirements.md and the tests' verifies: tags.

# Specification: System Requirements

## SYS-001
The system shall retrieve ADS-B state data for a circular area defined by a center latitude/longitude and a radius of up to 250 NM from the adsb.lol v2 API.
- Section: Ingest
- Verification Method: Demonstration
- Source: ConOps 3.1
- Verified By: tests/test_feed.py::test_area_validation; tests/test_feed.py::test_live_fetch_returns_aircraft_with_quality_fields

## SYS-002
The system shall store each poll as one timestamped JSON Lines record, including the capture area (center and radius), so analysis can be replayed offline.
- Section: Ingest
- Verification Method: Test
- Source: ConOps 3.1
- Verified By: tests/test_feed.py::test_each_poll_is_one_replayable_record; tests/test_report.py::test_indicators_judged_across_snapshots; tests/test_trend.py::test_captures_record_their_area

## SYS-003
The system shall not poll the public API more often than once every 5 seconds.
- Section: Ingest
- Verification Method: Test
- Source: ConOps 5
- Verified By: tests/test_feed.py::test_interval_is_clamped_to_minimum

## SYS-004
The system shall continue a capture when an individual poll fails, logging the failure.
- Section: Ingest
- Verification Method: Test
- Source: ConOps 5
- Verified By: tests/test_feed.py::test_failed_poll_does_not_stop_capture; tests/test_watch.py::test_run_writes_alert_log_and_survives_failed_poll

## SYS-005
The system shall read captures stored either as plain JSON Lines or gzip-compressed (.jsonl.gz).
- Section: Ingest
- Verification Method: Test
- Source: Architecture 4
- Verified By: tests/test_v2.py::test_gzip_capture_loads_like_plain

## SYS-006
On HTTP 429, 5xx or a timeout, the system shall retry a poll up to twice with backoff (honoring a numeric Retry-After, capped at 30 s), and shall not retry other client errors.
- Section: Ingest
- Verification Method: Test
- Source: Trade study risk: rate limiting
- Verified By: tests/test_feed.py::test_rate_limit_is_retried_with_backoff; tests/test_feed.py::test_gives_up_after_retries_and_never_retries_client_errors

## SYS-007
During collect and watch, the system shall warn when a poll returns fewer than 20% of the median aircraft count of the previous 10 polls (after at least 3 polls).
- Section: Ingest
- Verification Method: Test
- Source: Safety Risk Assessment HZ-8
- Verified By: tests/test_feed.py::test_feed_health_warns_on_collapse; tests/test_feed.py::test_collect_logs_feed_health_warning

## SYS-010
The system shall evaluate only direct 1090ES ADS-B (adsb_icao) and ADS-R (adsr_icao) reports, and shall count excluded report types (MLAT, TIS-B, Mode S) by type.
- Section: Performance checks (14 CFR 91.227(c)(1))
- Verification Method: Test
- Source: ConOps 3.2
- Verified By: tests/test_report.py::test_excluded_types_are_counted_not_evaluated; tests/test_rules.py::test_only_adsb_and_adsr_are_evaluated

## SYS-011
The system shall flag a NACp below 8 (position accuracy not better than 0.05 NM).
- Section: Performance checks (14 CFR 91.227(c)(1))
- Verification Method: Test
- Source: 91.227(c)(1)(i)
- Verified By: tests/test_report.py::test_verdicts; tests/test_rules.py::test_compliant_aircraft_passes_all_five; tests/test_rules.py::test_nacp_boundary; tests/test_rules.py::test_failures_cite_the_paragraph

## SYS-012
The system shall flag a NACv below 1 (velocity accuracy not better than 10 m/s).
- Section: Performance checks (14 CFR 91.227(c)(1))
- Verification Method: Test
- Source: 91.227(c)(1)(ii)
- Verified By: tests/test_rules.py::test_compliant_aircraft_passes_all_five; tests/test_rules.py::test_nacv_boundary; tests/test_rules.py::test_direct_adsb_nacv_zero_still_fails

## SYS-013
The system shall flag a NIC below 7 (containment radius not less than 0.2 NM).
- Section: Performance checks (14 CFR 91.227(c)(1))
- Verification Method: Test
- Source: 91.227(c)(1)(iii)
- Verified By: tests/test_rules.py::test_compliant_aircraft_passes_all_five; tests/test_rules.py::test_nic_boundary

## SYS-014
The system shall flag an SDA below 2 (design assurance worse than 1e-5 per flight hour).
- Section: Performance checks (14 CFR 91.227(c)(1))
- Verification Method: Test
- Source: 91.227(c)(1)(iv)
- Verified By: tests/test_rules.py::test_compliant_aircraft_passes_all_five; tests/test_rules.py::test_sda_boundary

## SYS-015
The system shall flag a SIL below 3 (integrity worse than 1e-7).
- Section: Performance checks (14 CFR 91.227(c)(1))
- Verification Method: Test
- Source: 91.227(c)(1)(v)
- Verified By: tests/test_report.py::test_verdicts; tests/test_rules.py::test_compliant_aircraft_passes_all_five; tests/test_rules.py::test_sil_boundary; tests/test_rules.py::test_failures_cite_the_paragraph

## SYS-016
The system shall report a missing indicator as "not reported", distinct from a failure.
- Section: Performance checks (14 CFR 91.227(c)(1))
- Verification Method: Test
- Source: ConOps 5
- Verified By: tests/test_report.py::test_verdicts; tests/test_rules.py::test_missing_indicator_is_not_a_failure

## SYS-017
The system shall not evaluate quality indicators from transmitters whose most frequently reported ADS-B version over the window is 0 or 1 (pre-DO-260B), and shall list them as "not evaluable" rather than failed.
- Section: Performance checks (14 CFR 91.227(c)(1))
- Verification Method: Test
- Source: 91.227(d); DO-260B
- Verified By: tests/test_report.py::test_pre_do260b_not_evaluable_not_failed; tests/test_report.py::test_version_judged_by_majority; tests/test_rules.py::test_pre_do260b_version_is_not_evaluated

## SYS-018
The system shall exclude airport surface vehicles (emitter category C1 to C3, or type code SERV) from 91.227 evaluation and count them as excluded.
- Section: Performance checks (14 CFR 91.227(c)(1))
- Verification Method: Test
- Source: 91.227 applies to aircraft
- Verified By: tests/test_report.py::test_surface_vehicle_excluded; tests/test_rules.py::test_surface_vehicles_are_recognized

## SYS-019
The system shall judge each indicator by its most frequent value over the capture window (ties go to the most recent value), shall note, as informational, indicators that switched between passing and failing values, and shall mark any failure that rests on such an indicator as low confidence.
- Section: Performance checks (14 CFR 91.227(c)(1))
- Verification Method: Test
- Source: Live-data finding: ADS-R NACv alternating 0/2
- Verified By: tests/test_report.py::test_indicators_judged_across_snapshots; tests/test_report.py::test_typical_value_is_most_frequent_ties_to_latest; tests/test_report.py::test_flip_flopping_indicator_judged_by_majority_and_noted; tests/test_report.py::test_failure_on_unstable_value_is_marked_low_confidence; tests/test_report.py::test_version_judged_by_majority; tests/test_report.py::test_single_bad_last_poll_does_not_decide_verdict

## SYS-021
For ADS-R targets, the system shall exclude NACv and NIC from evaluation (reporting them as excluded, not failed), because UAT-to-1090 converters used by aggregator feeders insert default values for both; NACp, SIL and SDA shall still be evaluated. ADS-R targets shall not take part in the interference screen.
- Section: Performance checks (14 CFR 91.227(c)(1))
- Verification Method: Test
- Source: Source review: uat2esnt.c:410, :351-361; readsb track.c:2188
- Verified By: tests/test_interference.py::test_adsr_targets_are_ignored; tests/test_report.py::test_adsr_converter_zeros_do_not_fail_or_flag_unstable; tests/test_rules.py::test_adsr_nacv_and_nic_excluded_others_judged; tests/test_rules.py::test_adsr_still_fails_on_nacp_and_sil; tests/test_rules.py::test_direct_adsb_nacv_zero_still_fails

## SYS-020
The system shall flag Mode A codes 7500, 7600 and 7700, and any non-"none" emergency status, with their meaning.
- Section: Emergency and track checks
- Verification Method: Test
- Source: 91.227(d)(9)
- Verified By: tests/test_report.py::test_markdown_cites_paragraphs_and_disclaimer; tests/test_rules.py::test_emergency_squawks; tests/test_rules.py::test_emergency_status_field

## SYS-030
The system shall flag a dropout when the feed reports an aircraft's position as older than the coast threshold (default 20 s) and a newer position arrives later, or when the aircraft is absent from one or more snapshots between two sightings. Gaps between the monitor's own polls shall not count as dropouts.
- Section: Emergency and track checks
- Verification Method: Test
- Source: ConOps 3.2
- Verified By: tests/test_tracks.py::test_stale_then_reacquired_is_a_dropout; tests/test_tracks.py::test_disappearance_is_a_dropout; tests/test_tracks.py::test_slow_poll_is_not_a_dropout; tests/test_tracks.py::test_steady_track_is_clean; tests/test_tracks.py::test_seen_pos_backdates_the_fix

## SYS-031
The system shall flag a position jump when consecutive positions imply a ground speed above 1,000 knots.
- Section: Emergency and track checks
- Verification Method: Test
- Source: ConOps 3.2
- Verified By: tests/test_tracks.py::test_steady_track_is_clean; tests/test_tracks.py::test_position_jump_detected; tests/test_tracks.py::test_airliner_speed_is_not_a_jump; tests/test_tracks.py::test_haversine_one_degree_latitude

## SYS-032
The system shall report tracks whose position goes stale and is never refreshed within the capture separately, as informational, and shall not count them as dropouts.
- Section: Emergency and track checks
- Verification Method: Test
- Source: ConOps 5
- Verified By: tests/test_tracks.py::test_stale_and_never_reacquired_is_a_lost_track_not_a_dropout

## SYS-033
The system shall remove the area trend of geometric-minus-barometric altitude against barometric altitude (Theil-Sen fit over airborne aircraft at or above 1,000 ft, at least 10 aircraft), compare each aircraft's remainder with the median remainder of its 8 nearest neighbors within 75 NM and 10,000 ft (aircraft with fewer than 4 such neighbors, or whose neighbors are all above or all below them, are counted as not assessed and never flagged), and flag aircraft more than 200 ft (configurable) off.
- Section: Emergency and track checks
- Verification Method: Test
- Source: ConOps 3.2
- Verified By: tests/test_v2.py::test_theil_sen_recovers_line_despite_outlier; tests/test_v2.py::test_trend_following_fleet_is_clean; tests/test_v2.py::test_outlier_flagged; tests/test_v2.py::test_regional_weather_shift_is_not_flagged; tests/test_v2.py::test_top_of_traffic_is_not_assessed; tests/test_v2.py::test_ground_and_missing_altitudes_ignored; tests/test_v2.py::test_too_few_aircraft_no_fit

## SYS-034
The system shall screen for possible GNSS interference by finding airborne, normally compliant aircraft (median NACp >= 8 and NIC >= 7 over the capture) that drop below those minimums in the same poll, and reporting groups of at least 3 such aircraft within 30 NM of each other.
- Section: Emergency and track checks
- Verification Method: Test
- Source: FAA GNSS interference concern; ConOps 3.2
- Verified By: tests/test_interference.py::test_simultaneous_nearby_drops_form_a_cluster; tests/test_interference.py::test_scattered_or_separate_drops_do_not_cluster; tests/test_interference.py::test_chronic_failures_are_not_events; tests/test_interference.py::test_aircraft_on_the_ground_are_ignored; tests/test_interference.py::test_adsr_targets_are_ignored; tests/test_interference.py::test_report_includes_screen

## SYS-035
On request, the system shall compare the aircraft-derived altitude trend with an independent weather-model estimate (Open-Meteo geopotential height minus ICAO standard pressure altitude, at standard pressure levels inside the capture's altitude range) and report the disagreement at each level.
- Section: Emergency and track checks
- Verification Method: Test
- Source: Independent validation of SYS-033
- Verified By: tests/test_weather.py::test_matches_icao_standard_atmosphere; tests/test_weather.py::test_rounds_to_nearest_hour; tests/test_weather.py::test_matching_trend_has_small_disagreement; tests/test_weather.py::test_wrong_trend_shows_large_disagreement; tests/test_weather.py::test_markdown_table; tests/test_weather.py::test_live_fetch

## SYS-036
Given FAA airspace data, the system shall determine for each aircraft whether it was seen in airspace where 14 CFR 91.225(d) requires ADS-B Out (Class B/C; within 30 NM of an Appendix D Section 1 airport up to 10,000 ft MSL; above Class B/C ceilings within their lateral limits up to 10,000 ft MSL; at or above 10,000 ft MSL), cite the paragraph, and state it next to each finding.
- Section: Emergency and track checks
- Verification Method: Test
- Source: 91.225(d); Part 91 Appendix D
- Verified By: tests/test_airspace.py::test_each_91_225_d_paragraph; tests/test_airspace.py::test_outside_rule_airspace; tests/test_airspace.py::test_ground_is_surface; tests/test_airspace.py::test_polygon_with_hole; tests/test_airspace.py::test_report_marks_rule_applicability; tests/test_airspace.py::test_committed_airspace_file_is_complete

## SYS-037
Given the FAA aircraft registry, the system shall build a lookup holding only Mode S address, year of manufacture, make, model and certification basis (never owner data), and shall break results out by certification basis and decade of manufacture.
- Section: Emergency and track checks
- Verification Method: Test
- Source: Shortfall root-cause analysis
- Verified By: tests/test_registry.py::test_build_keeps_aircraft_facts_only; tests/test_registry.py::test_analysis_breaks_out_certification_and_decade

## SYS-040
The system shall produce a Markdown report that cites the regulation paragraph for every failed indicator.
- Section: Reporting
- Verification Method: Test
- Source: ConOps 3.3
- Verified By: tests/test_report.py::test_markdown_cites_paragraphs_and_disclaimer

## SYS-041
The system shall export one CSV row per evaluated aircraft.
- Section: Reporting
- Verification Method: Test
- Source: ConOps 4
- Verified By: tests/test_report.py::test_csv_one_row_per_evaluated_aircraft

## SYS-042
Every report shall state that the data is crowdsourced and is not an FAA compliance determination.
- Section: Reporting
- Verification Method: Test
- Source: ConOps 5
- Verified By: tests/test_report.py::test_markdown_cites_paragraphs_and_disclaimer

## SYS-043
The system shall offer a redaction mode that replaces ICAO address, callsign and registration with stable pseudonyms, and published sample reports shall use it.
- Section: Reporting
- Verification Method: Test
- Source: ConOps 5
- Verified By: tests/test_report.py::test_identities_replaced_with_stable_pseudonyms; tests/test_trend.py::test_markdown_redacts_and_reports_rate; tests/test_v2.py::test_html_respects_redaction; tests/test_v2.py::test_csv_never_leaks_internal_key; tests/test_watch.py::test_redacted_alerts_hide_identity

## SYS-044
The system shall summarize results by emitter category, altitude band (surface, below 10,000 ft, 10,000 ft to FL180, FL180 and above, using each aircraft's highest altitude in the window) ADS-B version and report type (direct 1090ES vs ADS-R rebroadcast), and list aircraft types with at least one failure.
- Section: Reporting
- Verification Method: Test
- Source: 91.225 airspace boundaries
- Verified By: tests/test_v2.py::test_altitude_bands_follow_91_225; tests/test_v2.py::test_breakdowns_and_failing_types; tests/test_v2.py::test_band_uses_highest_altitude_seen

## SYS-045
The system shall produce a self-contained HTML report (no external resources) with a map of every evaluated aircraft's track colored by verdict, honoring redaction mode.
- Section: Reporting
- Verification Method: Test
- Source: ConOps 4
- Verified By: tests/test_v2.py::test_html_is_self_contained_with_map; tests/test_v2.py::test_html_respects_redaction

## SYS-046
Watch mode shall alert when an evaluated aircraft first shows an emergency code or emergency status, or changes to a different one, and shall not repeat the alert while it is unchanged.
- Section: Reporting
- Verification Method: Test
- Source: 91.227(d)(9)
- Verified By: tests/test_watch.py::test_emergency_alerts_once_per_change; tests/test_watch.py::test_excluded_targets_never_alert; tests/test_watch.py::test_run_writes_alert_log_and_survives_failed_poll

## SYS-047
Watch mode shall alert when an aircraft's 91.227(c)(1) result changes from pass to fail or fail to pass, or fails when first seen; it shall stay silent for steady aircraft, excluded targets and incomplete records.
- Section: Reporting
- Verification Method: Test
- Source: ConOps 6
- Verified By: tests/test_watch.py::test_steady_fleet_is_silent; tests/test_watch.py::test_degradation_and_recovery; tests/test_watch.py::test_fail_on_first_sight; tests/test_watch.py::test_fields_persist_between_polls; tests/test_watch.py::test_excluded_targets_never_alert; tests/test_watch.py::test_redacted_alerts_hide_identity

## SYS-048
Watch mode shall confirm a pass/fail change only after it holds for a configurable number of consecutive polls (default 2), and shall record a failure that clears before confirmation as a TRANSIENT event instead of discarding it.
- Section: Reporting
- Verification Method: Test
- Source: Alert-fatigue finding, first live watch run
- Verified By: tests/test_watch.py::test_degradation_and_recovery; tests/test_watch.py::test_single_poll_blip_is_transient_not_degraded; tests/test_watch.py::test_confirm_one_alerts_immediately

## SYS-053
The system shall re-analyze any set of captures with the current rules and report, per capture in time order: area, duration, aircraft, pass rate, high-confidence and low-confidence failures, failures inside rule airspace, not-evaluable and ADS-R counts, interference clusters and altitude outliers.
- Section: Reporting
- Verification Method: Test
- Source: Shortfall Analysis recommendation 1
- Verified By: tests/test_trend.py::test_one_row_per_capture_in_time_order; tests/test_trend.py::test_markdown_redacts_and_reports_rate; tests/test_trend.py::test_old_captures_without_area_still_work

## SYS-054
Across captures, the system shall list every aircraft with a high-confidence failure, and every aircraft flagged by the altitude check, with its record in each capture where it was seen, ranking aircraft flagged in more captures first.
- Section: Reporting
- Verification Method: Test
- Source: Shortfall Analysis recommendation 1
- Verified By: tests/test_trend.py::test_recurring_failure_ranks_first; tests/test_trend.py::test_markdown_redacts_and_reports_rate

## SYS-050
The build shall generate the traceability matrix from test tags and fail if any requirement is unverified.
- Section: Engineering
- Verification Method: Test
- Source: This document
- Verified By: tests/test_rtm.py::test_every_requirement_in_this_repo_is_verified; tests/test_rtm.py::test_unverified_requirement_is_reported

## SYS-051
Continuous integration shall run the test suite and the traceability gate on every push, and fail if the committed RTM differs from the generated one.
- Section: Engineering
- Verification Method: Test
- Source: This document
- Verified By: tests/test_v2.py::test_ci_runs_tests_and_traceability_gate

## SYS-052
The system shall export every requirement, its section, verification method, source and verifying tests as a ReqIF 1.2 file that validates against the OMG schema, with every internal reference resolving; CI shall fail if the committed export differs from a fresh one.
- Section: Engineering
- Verification Method: Test
- Source: Tool interchange (DOORS, Jama, Polarion)
- Verified By: tests/test_reqif.py::test_every_requirement_exported_in_order; tests/test_reqif.py::test_identifiers_unique_and_references_resolve; tests/test_reqif.py::test_attribute_values_carry_requirement_content; tests/test_reqif.py::test_export_is_deterministic_and_committed_copy_is_current; tests/test_reqif.py::test_header_declares_reqif_1_0_content

## SYS-055
A scheduled weekly workflow shall download the most recent 7 daily captures, run the trend analysis with identities redacted, and publish the result as a build artifact, using read-only repository permissions.
- Section: Engineering
- Verification Method: Test
- Source: Shortfall Analysis recommendation 1
- Verified By: tests/test_v2.py::test_weekly_trend_workflow

## SYS-060
The system shall use only the Python standard library at runtime.
- Section: Engineering
- Verification Method: Inspection
- Source: Architecture 4
- Verified By: tests/test_report.py::test_runtime_imports_are_stdlib
